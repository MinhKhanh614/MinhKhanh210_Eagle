//======================================================
// ALIGN v 1.0.2
//
// Eagle v5.7 or later is required. Only the board editor is supported.
//
// Aligns board components in group or listed at the command line
// The direction of alignment is autodetected. The components are aligned
// after the origins of the top or leftmost component
//
// This software is released under the BSD 4-clause license:
//
// Copyright (c) 2010-2011, Damhave Systems
// All rights reserved.

// Modified 2010-05-21 LJW - Correct group coordinate determination & quote output script name on exit

// Redistribution and use in source and binary forms, with or without modification, are permitted provided that the following conditions are met:

//	*	Redistributions of source code must retain the above copyright notice, this list of conditions and the following disclaimer.
//	*	Redistributions in binary form must reproduce the above copyright notice, this list of conditions and the following disclaimer
// 		in the documentation and/or other materials provided with the distribution.
//	*	Neither the name of the Damhave Systems nor the names of its contributors may be used to endorse or promote products derived from
//	    this software without specific prior written permission.
// THIS SOFTWARE IS PROVIDED BY THE COPYRIGHT HOLDERS AND CONTRIBUTORS "AS IS" AND ANY EXPRESS OR IMPLIED WARRANTIES, INCLUDING, BUT NOT LIMITED TO,
// THE IMPLIED WARRANTIES OF MERCHANTABILITY AND FITNESS FOR A PARTICULAR PURPOSE ARE DISCLAIMED. IN NO EVENT SHALL THE COPYRIGHT HOLDER OR CONTRIBUTORS
// BE LIABLE FOR ANY DIRECT, INDIRECT, INCIDENTAL, SPECIAL, EXEMPLARY, OR CONSEQUENTIAL DAMAGES (INCLUDING, BUT NOT LIMITED TO, PROCUREMENT OF SUBSTITUTE
// GOODS OR SERVICES; LOSS OF USE, DATA, OR PROFITS; OR BUSINESS INTERRUPTION) HOWEVER CAUSED AND ON ANY THEORY OF LIABILITY, WHETHER IN CONTRACT,
// STRICT LIABILITY, OR TORT (INCLUDING NEGLIGENCE OR OTHERWISE) ARISING IN ANY WAY OUT OF THE USE OF THIS SOFTWARE, EVEN IF ADVISED OF THE POSSIBILITY
// OF SUCH DAMAGE.
//======================================================
#usage	"<B>Aligns board components in group or listed at the command line</B>"
"<P>"
	"<P>"
	"Align components along a line parallel to the x or y axis of the board.<br>"
	"The direction of alignment is autodetected by looking at the position of the components. The alignment direction can also be forced.<br><br>"
	"<b>Usage:</b>"
	"<blockquote>run align<br>"
	"run align [-flag{flag}] [increment] [ref object] {component}</blockquote>"
	"<b>Flags:</b>"
	"<blockquote>c: align to the bottommost/leftmost Component in group or list<br>"	
	"d: Distribute components evenly between the outermost components<br>"	
	"e: use regular Expressions (regex) instead of wildcards<br>"	
	"g: align to Grid<br>"	
	"h: Force alignment on a horizontal line<br>"	
	"i: Increment position for each component by the specified value<br>"	
	"o: align to reference Object<br>"	
	"s: Snap to grid<br>"
	"v: Force alignment on a Vertical line</blockquote>"	
	"<I>The components in the selection group are used when no components are specified at the command line.<br>"
	"The align to the bottommost/leftmost component flag -c is default set if no -g or -o flags are specified</I></blockquote>"
	"<P>"
	"<b>Examples:</b><br>"
	"Align the selected components to the bottommost leftmost component, force alignment on a vertical line:"
	"<blockquote>run align -v</blockquote>"
	"Align the resistors R1, R2, R3 on a horizontal line and snap to grid:"
	"<blockquote>run align -hg R1 R2 R3</blockquote>"
	"Align the connectors J1, J2 and J4 to the hole H2:"	
	"<blockquote>run align -o H2 J1 J2 J4</blockquote>"	
	"Align the selected components to the bottommost leftmost component, increment the position with 0.5 for each component:"
	"<blockquote>run align -i 0.5</blockquote>"	
	"Align all LEDs to the nearest grid line and distribute them evenly along the line:"
	"<blockquote>run align -gd LED*</blockquote>"
	"Align all LEDs to the nearest grid line and snap to the grid points along the line:"
	"<blockquote>run align -gs LED*</blockquote>"
	"<P>"
	"Copyright (c) 2010-2011 Damhave Systems"
	"<P>"
	"<Author>Danny Damhave<br>Damhave Systems<br>www.damhave.com</Author><br><br>"
	"This ulp is released under the BSD 4-clause license. See source code for details!"

enum {false, true};
enum {ALIGN_ALONG_YAXIS, ALIGN_ALONG_XAXIS};
enum {GROUP, LIST};
string outputFileName = "aligntempfile.scr";
int alignment, xRefObject = INT_MAX, yRefObject = INT_MAX, xAligned = INT_MAX, yAligned = INT_MAX, xMin = INT_MAX, xMax = INT_MIN, yMax = INT_MIN, yMin = INT_MAX, noElements = 0, mode = GROUP, firstInList = 1,
	alignToComponentFlag = true, alignToGridFlag = false, alignToObjectFlag = false, alignOnVerticalLine = false, alignOnHorizontalLine = false, regexFlag = false, snapFlag = false, distributeFlag = false, incrementFlag = false;
real distance, increment, xAvg = 0.0, yAvg = 0.0;

int isMatch(string s, string test, int useRegex)
{	
	string regex = !useRegex ?  "^" : test;
	if (!useRegex)
	{
		for(int i = 0; test[i];)
		{
			switch(test[i])
			{
				case '[': regex += strsub(test, i, strchr(test, ']', i) - i + 1), i += strchr(test, ']', i) - i + 1; break;
				case '?': regex += ".", i++; break;
				case '*': regex += ".*", i++; break;
				case '+': case '^': case '$': case '.': case '{': case '}': case '(': case ')':  case '|': case '\\':
				regex += "\\" + test[i], i++; break;
				default: regex += test[i], i++;
			}
		}
		regex +='$';
	}
	return strxstr(s, regex, 0) == 0;
}

int inList(string name)
{
	for(int i = firstInList; i < argc && argv[i] != ""; i++)
	{
		if (regexFlag)
		{
			if (isMatch(name, argv[i], regexFlag)) return true;
		}
		else
		{
			if (isMatch(strupr(name), strupr(argv[i]), regexFlag)) return true;		
		}
	}
	return false;
}

int snapToGrid(UL_BOARD brd, real coordinate)
{
	real gSize;
	if (brd.grid.unitdist == GRID_UNIT_MIC) gSize = brd.grid.distance * 10;
	else if  (brd.grid.unitdist == GRID_UNIT_MM) gSize = brd.grid.distance * 10000;
	else if  (brd.grid.unitdist == GRID_UNIT_MIL) gSize = brd.grid.distance * 254;
	else if  (brd.grid.unitdist == GRID_UNIT_INCH) gSize = brd.grid.distance * 254000;
	return (round (coordinate / gSize) * gSize);	
}

real input2u(UL_BOARD brd, real inputValue)
{
	real convFactor;
	if (brd.grid.unitdist == GRID_UNIT_MIC) convFactor = 10;
	else if  (brd.grid.unitdist == GRID_UNIT_MM) convFactor = 10000;
	else if  (brd.grid.unitdist == GRID_UNIT_MIL) convFactor = 254;
	else if  (brd.grid.unitdist == GRID_UNIT_INCH) convFactor = 254000;
	return (round (inputValue * convFactor));	
}

//		***** The ulp begins here *****
if (!board && !dlgMessageBox("Can only be used in the board editor.\n")) exit(1);
if (EAGLE_VERSION < 5 || (EAGLE_VERSION == 5 && EAGLE_RELEASE < 7) && !dlgMessageBox("Requires Eagle v5.7 or later.\n")) exit(1);

if (argc>firstInList)
{
	string flags = argv[firstInList];
	if (flags[0] == '-')
	{
		if (strlen(flags) == 1) { dlgMessageBox("No flags.\n"); exit(1); }		
		for (int i = 1; flags[i]; i++)
		{
			switch (flags[i])
			{
				case 'c' : alignToComponentFlag = true; break;
				case 'd' : distributeFlag = true; break;
				case 'e' : regexFlag = true; break;
				case 'g' : alignToGridFlag = true; alignToComponentFlag = false; break;
				case 'h' : alignOnHorizontalLine = true; break;
				case 'i' : incrementFlag = true; break;
				case 'o' : alignToObjectFlag = true; alignToComponentFlag = false; break;
				case 's' : snapFlag = true; break;
				case 'v' : alignOnVerticalLine = true; break;
				default : dlgMessageBox("No such flag.\n"); exit(3);
			}
		}	 
		firstInList++;
		if (((alignOnHorizontalLine && alignOnVerticalLine) || (incrementFlag && distributeFlag) || (alignToGridFlag && alignToObjectFlag) || (alignToComponentFlag && alignToObjectFlag) || (alignToGridFlag && alignToComponentFlag)) && !dlgMessageBox("Illegal flag combination.\n")) exit(1);
		if (incrementFlag)
		{
			if (!(argc>firstInList)  && !dlgMessageBox("No increment specified.\n")) exit(1);
			board(brd) { increment = input2u(brd, strtod(argv[firstInList])); }
			firstInList++;
		}
		if (alignToObjectFlag)
		{
			if (!(argc>firstInList)  && !dlgMessageBox("No object specified.\n")) exit(1);
			board(brd) { brd.elements(element) { if (element.name == argv[firstInList]) xRefObject = element.x, yRefObject = element.y; } }
			if ((xRefObject == INT_MAX && yRefObject == INT_MAX) && !dlgMessageBox("No such object.\n")) exit(1);
			firstInList++;
		}		
	}
	else;	// There are no flags therefore use the default align to bottommost/leftmost object in the direction with the most spread
}
if (argc>firstInList) mode = LIST;

board(brd)
{
	outputFileName = filedir(brd.name)+outputFileName;
	output(outputFileName, "wtD")
	{
		status("Aligning Objects...");
		brd.elements(element)
		{
			if ((mode == GROUP && ingroup(element)) || (mode == LIST && inList(element.name)))
			{
				noElements += 1;
				if (element.x < xMin) xMin = element.x;
				if (element.x > xMax) xMax = element.x;
				if (element.y < yMin) yMin = element.y;
				if (element.y > yMax) yMax = element.y;
				xAvg += element.x;
				yAvg += element.y;				
			}
		}
		if ((noElements < 2) && !dlgMessageBox("Minimum 2 objects in group/list required.\n")) exit(1);
		xAvg = xAvg / noElements;
		yAvg = yAvg / noElements;

		if (alignOnHorizontalLine) alignment = ALIGN_ALONG_XAXIS;									// Alignment in X direction forced by -h flag ?
		else if (alignOnVerticalLine) alignment = ALIGN_ALONG_YAXIS;								// Alignment in Y direction forced by -v flag ?
		else alignment = ((xAvg - xMin) > (yMax - yAvg)) ? ALIGN_ALONG_XAXIS : ALIGN_ALONG_YAXIS;	// Alignment autodetected on basis of spread
		
		if (alignment == ALIGN_ALONG_YAXIS)
		{
			if (alignToObjectFlag) xAligned = xRefObject;											// Align on a vertical line going through the reference object ?
			else brd.elements(element)																// Align on a vertical line going through to the leftmost bottommost object
			{
				if ((mode == GROUP && ingroup(element)) || (mode == LIST && inList(element.name)))
				{
					if (element.y == yMin) xAligned = (snapFlag || alignToGridFlag) ? snapToGrid(brd, element.x) : ((element.x < xAligned) ? element.x : xAligned);
				}
			}
			if (distributeFlag)
				distance = (yMax - yMin)/(noElements-1);
			else if (incrementFlag)
				distance = increment;			 
		}
		else
		{
			if (alignToObjectFlag) yAligned = yRefObject;											// Align on a horizontal line going through the reference object ?
			else brd.elements(element)																// Align on a horizontal line going through to the leftmost bottommost object
			{
				if ((mode == GROUP && ingroup(element)) || (mode == LIST && inList(element.name)))
				{
					if (element.x == xMin) yAligned = (snapFlag || alignToGridFlag) ? snapToGrid(brd, element.y) : ((element.y < yAligned) ? element.y : yAligned);
				}
			}
			if (distributeFlag)
				distance = (xMax - xMin)/(noElements-1); 
			else if (incrementFlag)
				distance = increment;			 
		}
								
		int n = 0, totalDistance;
		brd.elements(element)
		{
			if ((mode == GROUP && ingroup(element)) || (mode == LIST && inList(element.name)))
			{
				if (distributeFlag || incrementFlag)
				{
					totalDistance = ((alignment == ALIGN_ALONG_YAXIS) ? yMin : xMin) + distance * n;
					if (alignment == ALIGN_ALONG_YAXIS) printf("MOVE %s (%fmil %fmil)\n", element.name, u2mil(xAligned), u2mil(totalDistance));			
					else printf("MOVE %s (%fmil %fmil)\n", element.name, u2mil(totalDistance), u2mil(yAligned));
					n++;
				}
				else
				{
					if (alignment == ALIGN_ALONG_YAXIS) printf("MOVE %s (%fmil %fmil)\n", element.name, u2mil(xAligned), u2mil(snapFlag ? snapToGrid(brd, element.y) : element.y));			
					else printf("MOVE %s (%fmil %fmil)\n", element.name, u2mil(snapFlag ? snapToGrid(brd, element.x) : element.x), u2mil(yAligned));
				}
			}
		}
	}
}
exit("script '" + outputFileName + "'");
