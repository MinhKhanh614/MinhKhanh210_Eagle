#usage "Trace layer, to display layers step by step.<p>"
       "RUN trace-layer_kxn +<br>"
       "RUN trace-layer_kxn -<br>"
       "Layers 17 Pad, 18 Via, 19 Unrouted, 23 tOrigin and 24 bOrigin are not separated displayed"

// Version 1.0  - 2007.06.06 support@cadsoft.de

int    supplyLayer[];
int    usedLayer[];
int    mLayer = 0;
int    lastUsed;

int gerberLayer[] =           {1  , 16  , 17  , 18  , 20  , 21  , 22  , 25  , 26  , 27  , 28  , 29  , 30};
int colorGerberLayer_old[] =  {4  , 1   , 2   , 14  , 15  , 7   , 7   , 7   , 7   , 7   , 7   , 7   , 7};
int fillGerberLayer_old[] =   {1  , 1   , 1   , 1   , 1   , 1   , 1   , 1   , 1   , 1   , 1   , 3   , 6};

// int colorGerberLayer[] =      {4  , 1   , 4   , 4  , 15  , 7   , 7   , 7   , 7   , 7   , 7   , 7   , 7};
// int fillGerberLayer[] =       {1  , 1   , 1   , 1   , 1   , 1   , 1   , 1   , 1   , 1   , 1   , 3   , 6};

int color_TOP_COPPER = 4;
int color_BOT_COPPER = 1;

int color_TOP_SILKSCREEN = 2;
int color_BOT_SILKSCREEN = 6;

int color_TOP_SOLDERMASK = 3;
int color_BOT_SOLDERMASK = 14;

int fill_TOP = 1;

string cmd;
string message = "";
string kxnLayer[] = {
                "DISPLAY ALL;",
                "DISPLAY NONE 1 17 18 19 20 23 29;", // di day TOP                         1
                "DISPLAY NONE 16 17 18 19 20 24 30;", // di day BOT                        2
                "DISPLAY NONE 1 16 17 18 19 20 23 24 29 30;", // di day                       3

                "DISPLAY NONE 17 18 19 20 21 23 25 27 29;",          // Xep LK TOP      4
                "DISPLAY NONE 17 18 19 20 22 24 26 28 30;",          // Xep LK BOT      5

                "DISPLAY NONE 19 20 21 25 27;",          // Xem chu TOP              6
                "DISPLAY NONE 17 18 19 20 21 25 27;",          // Xep chu TOP        7
                "DISPLAY NONE 19 20 22 26 28;",          // Xem chu BOT              8
                "DISPLAY NONE 17 18 19 20 22 26 28;",          // Xep chu BOT        9

                "DISPLAY NONE 1 17 18;",         // Xem gerber TOP COPPER               10
                "DISPLAY NONE 16 17 18;",         // Xem gerber BOT COPPER              11
                "DISPLAY NONE 21 25 27;",         // Xem gerber TOP SILKSCREEN          12
                "DISPLAY NONE 22 26 28;",         // Xem gerber BOT SILKSCREEN          13
                "DISPLAY NONE 29;",         // Xem gerber TOP Soldermask                14
                "DISPLAY NONE 30;",         // Xem gerber BOT Soldermask                15
                "DISPLAY NONE 20 44 45;"          // Xem gerber Drill                   16
};
int count_Layerkxn = 0;
for(int cf = 0; kxnLayer[cf]; ++cf){
    count_Layerkxn++;
}
// string tt = "";
// sprintf(tt, "%d", count_Layerkxn);
// dlgMessageBox(tt);

string layerFile = filesetext(argv[0], ".trl");
string f[];
int    isFile = fileglob(f, layerFile);

void collectlayer(void) {
    string tempStringLine = "";
    board(B) B.layers(L) {

        int layer_color = L.color;
        int layer_fill = L.fill;
        string layer_name = L.name;
        int layer_number = L.number;
        int layer_used = L.used;
        int layer_visible = L.visible;
        string tempString = "";

        sprintf(tempString, "color: %d - fill: %d - name: %s - num: %d - used: %d - visible: %d \n",
                            layer_color, layer_fill, layer_name, layer_number, layer_used, layer_visible);
        tempStringLine += tempString;                            

        if(mLayer >= 10){
          if(L.number == 1 || L.number == 17 || L.number == 18){ // Top copper
            L.color = color_TOP_COPPER;
            L.fill = fill_TOP;
          }else if(L.number == 16 || L.number == 17 || L.number == 18){ // BOT copper
            L.color = color_BOT_COPPER;
            L.fill = fill_TOP;
          }else if(L.number == 21 || L.number == 25 || L.number == 27){ // TOP Silkscreen
            L.color = color_TOP_SILKSCREEN;
            L.fill = fill_TOP;
          }else if(L.number == 22 || L.number == 26 || L.number == 28){ // BOT Silkscreen
            L.color = color_BOT_SILKSCREEN;
            L.fill = fill_TOP;
          }else if(L.number == 29){                                     // TOP Soldermask
            L.color = color_TOP_SOLDERMASK;
            L.fill = fill_TOP;
          }else if(L.number == 30){                                     // BOT Soldermask
            L.color = color_BOT_SOLDERMASK;
            L.fill = fill_TOP;
          }

        }else{
          for(int cf2 = 0; gerberLayer[cf2]; ++cf2){
              if(gerberLayer[cf2] == L.number){
                L.color = colorGerberLayer_old;
                L.fill = fillGerberLayer_old;
                break;
              }
          }
        }
        // if (L.used) {
        // fromName[fcntLay] = L.name;
        // fromlNumber[fcntLay] = L.number;
        // fcntLay++;
        // fromName[fcntLay] = "";
        // fromlNumber[fcntLay] = 0;
        // }
        // toName[cntLay] = L.name;
        // lNumber[cntLay] = L.number;
        // cntLay++;
        // toName[cntLay] = "";
        // lNumber[cntLay] = 0;
    }

    // dlgDialog("trace-layer_kxn 1.1 Demo") {
    // dlgHBoxLayout dlgSpacing(350);
    // dlgTextEdit(tempStringLine);
    // // dlgLabel(tempStringLine);
    // dlgHBoxLayout {
    //     dlgPushButton("+Ok") dlgAccept();
    //     dlgPushButton("-Cancel") dlgReject();
    //     }
    // };
  

    return;
}

void checkLayer(void) {
  if (argv[1] == "+") {
    // if (mLayer == 23 || mLayer == 24) mLayer = 25;
    // if (mLayer == 17 || mLayer == 18 || mLayer == 19) mLayer = 20;
    lastUsed = mLayer;
  }
  if (argv[1] == "-") {
    // if (mLayer == 23 || mLayer == 24) mLayer = 22;
    // if (mLayer == 17 || mLayer == 18 || mLayer == 19) mLayer = 16;
    lastUsed = mLayer;
  }
  return;
}

if (isFile) {
  string rLayer;
  int n = fileread(rLayer, layerFile);
  mLayer = strtol(rLayer);
  if(mLayer >= count_Layerkxn){
      mLayer = count_Layerkxn - 1;
  }
}

string tt = "";
sprintf(tt, "%d", mLayer);
// dlgMessageBox(tt);

if (argv[1] == "-") {
  mLayer --;
  if (board) {
        sprintf(tt, "--%d", mLayer);
        // dlgMessageBox(tt);
    if (mLayer <= 0) {
        // if (mLayer < 1) {
    //   if (!mLayer) message = "The first layer.";
    //   mLayer = 1;
      mLayer = 0;
    }
  }
  else if (schematic) {
    if (mLayer < 91) mLayer = 91;
  }
}

if (argv[1] == "+") {
  mLayer ++;
//   if (mLayer >255) {
  if(mLayer > count_Layerkxn){
    mLayer = count_Layerkxn - 1;
    // if (!mLayer) message = "The last layer.";
  }
}


checkLayer();
if (board) {
  board(B) {
    // B.layers(L) {
    //   if (L.used) {
    //     usedLayer[L.number] = 1;
    //   }
    //   string ln = L.name;
    //   if (ln[0] == '$') {
    //     usedLayer[L.number] = 1;
    //     supplyLayer[L.number] = 1;
    //   }
    // }
    // if (argv[1] == "+") {
    //   if (!usedLayer[mLayer]) {
    //     do {
    //       mLayer++;
    //       if (usedLayer[mLayer]) break;
    //     } while (mLayer < 256);
    //     if (mLayer >= 255) message = "The last Layer.";
    //   }
    // }
    // if (argv[1] == "-") {
    //   if (!usedLayer[mLayer]) {
    //     do {
    //       mLayer--;
    //       if (usedLayer[mLayer]) break;
    //     } while (mLayer > 1);
    //   }
    // }

    checkLayer();
    // if (usedLayer[mLayer]) {
    //   if (mLayer < 17) {
      if (mLayer < count_Layerkxn) {
        // if (supplyLayer[mLayer]) {
        //   sprintf(cmd, "DISPLAY NONE %d;\n", mLayer);
        //   message ="<font color=\"red\"><b>ATTENTION</b></font> this is a <b>Supply</b> layer, <b>do not use</b> this Layer in CAM-Job with <b>Pad</b>- and/or <b>Via</b>-Layer.";
        // }
        // else {
        //   sprintf(cmd, "DISPLAY NONE %d 17 18;\n", mLayer);
        // }
        sprintf(tt, "arr%d", mLayer);
        // dlgMessageBox(tt);
        collectlayer();
        cmd = kxnLayer[mLayer];
      }
    //   else {
    //     sprintf(cmd, "DISPLAY NONE %d;\n", mLayer);
    //   }
      lastUsed = mLayer;
    // }
  }
}
checkLayer();
if (lastUsed >= 0) {
  output(layerFile, "wtD") {
    printf("%d", lastUsed);

    // dlgDialog("trace-layer_kxn Demo") {
    // dlgHBoxLayout dlgSpacing(350);
    // // dlgTextEdit(cmd);
    // dlgLabel(cmd);
    // dlgHBoxLayout {
    //     dlgPushButton("+Ok") dlgAccept();
    //     dlgPushButton("-Cancel") dlgReject();
    //     }
    // }; 

  }
}
// if (message) {
//   string s;
//   sprintf(s, "RUN ulpmessage '%s';\n", message);
//   cmd += s;

  
// }

// DISPLAY NONE 20;  // display layer cmd

// //////////////////////////////////////////////////
// color: 4 - fill: 1 - name: Top - num: 1 - used: 1 - visible: 1 
// color: 1 - fill: 3 - name: Route2 - num: 2 - used: 0 - visible: 0 
// color: 4 - fill: 3 - name: Route3 - num: 3 - used: 0 - visible: 0 
// color: 1 - fill: 4 - name: Route4 - num: 4 - used: 0 - visible: 0 
// color: 4 - fill: 4 - name: Route5 - num: 5 - used: 0 - visible: 0 
// color: 1 - fill: 8 - name: Route6 - num: 6 - used: 0 - visible: 0 
// color: 4 - fill: 8 - name: Route7 - num: 7 - used: 0 - visible: 0 
// color: 1 - fill: 2 - name: Route8 - num: 8 - used: 0 - visible: 0 
// color: 4 - fill: 2 - name: Route9 - num: 9 - used: 0 - visible: 0 
// color: 1 - fill: 7 - name: Route10 - num: 10 - used: 0 - visible: 0 
// color: 4 - fill: 7 - name: Route11 - num: 11 - used: 0 - visible: 0 
// color: 1 - fill: 5 - name: Route12 - num: 12 - used: 0 - visible: 0 
// color: 4 - fill: 5 - name: Route13 - num: 13 - used: 0 - visible: 0 
// color: 1 - fill: 6 - name: Route14 - num: 14 - used: 0 - visible: 0 
// color: 4 - fill: 6 - name: Route15 - num: 15 - used: 0 - visible: 0 
// color: 1 - fill: 1 - name: Bottom - num: 16 - used: 1 - visible: 0 
// color: 2 - fill: 1 - name: Pads - num: 17 - used: 1 - visible: 1 
// color: 14 - fill: 1 - name: Vias - num: 18 - used: 1 - visible: 1 
// color: 6 - fill: 1 - name: Unrouted - num: 19 - used: 0 - visible: 1 
// color: 15 - fill: 1 - name: Dimension - num: 20 - used: 1 - visible: 1 
// color: 7 - fill: 1 - name: tPlace - num: 21 - used: 1 - visible: 0 
// color: 7 - fill: 1 - name: bPlace - num: 22 - used: 1 - visible: 0 
// color: 15 - fill: 1 - name: tOrigins - num: 23 - used: 1 - visible: 1 
// color: 15 - fill: 1 - name: bOrigins - num: 24 - used: 1 - visible: 0 
// color: 7 - fill: 1 - name: tNames - num: 25 - used: 1 - visible: 0 
// color: 7 - fill: 1 - name: bNames - num: 26 - used: 1 - visible: 0 
// color: 7 - fill: 1 - name: tValues - num: 27 - used: 1 - visible: 0 
// color: 7 - fill: 1 - name: bValues - num: 28 - used: 1 - visible: 0 
// color: 7 - fill: 3 - name: tStop - num: 29 - used: 1 - visible: 1 
// color: 7 - fill: 6 - name: bStop - num: 30 - used: 1 - visible: 0 
// color: 7 - fill: 4 - name: tCream - num: 31 - used: 1 - visible: 0 
// color: 7 - fill: 5 - name: bCream - num: 32 - used: 0 - visible: 0 
// color: 6 - fill: 3 - name: tFinish - num: 33 - used: 0 - visible: 0 
// color: 6 - fill: 6 - name: bFinish - num: 34 - used: 0 - visible: 0 
// color: 7 - fill: 4 - name: tGlue - num: 35 - used: 1 - visible: 0 
// color: 7 - fill: 5 - name: bGlue - num: 36 - used: 0 - visible: 0 
// color: 7 - fill: 1 - name: tTest - num: 37 - used: 0 - visible: 0 
// color: 7 - fill: 1 - name: bTest - num: 38 - used: 0 - visible: 0 
// color: 4 - fill: 11 - name: tKeepout - num: 39 - used: 1 - visible: 0 
// color: 1 - fill: 11 - name: bKeepout - num: 40 - used: 0 - visible: 0 
// color: 4 - fill: 10 - name: tRestrict - num: 41 - used: 1 - visible: 0 
// color: 1 - fill: 10 - name: bRestrict - num: 42 - used: 0 - visible: 0 
// color: 2 - fill: 10 - name: vRestrict - num: 43 - used: 0 - visible: 0 
// color: 7 - fill: 1 - name: Drills - num: 44 - used: 1 - visible: 0 
// color: 7 - fill: 1 - name: Holes - num: 45 - used: 1 - visible: 0 
// color: 3 - fill: 1 - name: Milling - num: 46 - used: 0 - visible: 0 
// color: 7 - fill: 1 - name: Measures - num: 47 - used: 0 - visible: 0 
// color: 7 - fill: 1 - name: Document - num: 48 - used: 0 - visible: 0 
// color: 7 - fill: 1 - name: Reference - num: 49 - used: 0 - visible: 0 
// color: 7 - fill: 1 - name: dxf - num: 50 - used: 0 - visible: 0 
// color: 7 - fill: 1 - name: tDocu - num: 51 - used: 1 - visible: 0 
// color: 7 - fill: 1 - name: bDocu - num: 52 - used: 0 - visible: 0 
// color: 7 - fill: 9 - name: tGND_GNDA - num: 53 - used: 0 - visible: 0 
// color: 1 - fill: 9 - name: bGND_GNDA - num: 54 - used: 0 - visible: 0 
// color: 7 - fill: 1 - name: wert - num: 56 - used: 0 - visible: 0 
// color: 7 - fill: 1 - name: tCAD - num: 57 - used: 0 - visible: 0 
// color: 7 - fill: 1 - name: tCarbon - num: 59 - used: 0 - visible: 0 
// color: 7 - fill: 1 - name: bCarbon - num: 60 - used: 0 - visible: 0 
// color: 9 - fill: 1 - name: SimResults - num: 88 - used: 0 - visible: 0 
// color: 9 - fill: 1 - name: SimProbes - num: 89 - used: 0 - visible: 0 
// color: 5 - fill: 1 - name: Modules - num: 90 - used: 0 - visible: 0 
// color: 7 - fill: 1 - name: Muster - num: 100 - used: 0 - visible: 0 
// color: 12 - fill: 4 - name: Patch_Top - num: 101 - used: 0 - visible: 0 
// color: 7 - fill: 1 - name: Vscore - num: 102 - used: 0 - visible: 0 
// color: 7 - fill: 1 - name: tMap - num: 103 - used: 0 - visible: 0 
// color: 16 - fill: 1 - name: Name - num: 104 - used: 0 - visible: 0 
// color: 7 - fill: 1 - name: tPlate - num: 105 - used: 0 - visible: 0 
// color: 7 - fill: 1 - name: bPlate - num: 106 - used: 0 - visible: 0 
// color: 7 - fill: 1 - name: Crop - num: 107 - used: 0 - visible: 0 
// color: 10 - fill: 1 - name: tplace-old - num: 108 - used: 0 - visible: 0 
// color: 11 - fill: 1 - name: ref-old - num: 109 - used: 0 - visible: 0 
// color: 7 - fill: 1 - name: fp0 - num: 110 - used: 0 - visible: 0 
// color: 7 - fill: 1 - name: LPC17xx - num: 111 - used: 0 - visible: 0 
// color: 7 - fill: 1 - name: tSilk - num: 112 - used: 0 - visible: 0 
// color: 7 - fill: 1 - name: IDFDebug - num: 113 - used: 0 - visible: 0 
// color: 7 - fill: 1 - name: Badge_Outline - num: 114 - used: 0 - visible: 0 
// color: 7 - fill: 1 - name: ReferenceISLANDS - num: 115 - used: 0 - visible: 0 
// color: 9 - fill: 4 - name: Patch_BOT - num: 116 - used: 0 - visible: 0 
// color: 7 - fill: 1 - name: Rect_Pads - num: 118 - used: 0 - visible: 0 
// color: 7 - fill: 1 - name: _tsilk - num: 121 - used: 0 - visible: 0 
// color: 7 - fill: 1 - name: _bsilk - num: 122 - used: 0 - visible: 0 
// color: 7 - fill: 1 - name: tTestmark - num: 123 - used: 0 - visible: 0 
// color: 7 - fill: 1 - name: bTestmark - num: 124 - used: 0 - visible: 0 
// color: 7 - fill: 1 - name: _tNames - num: 125 - used: 0 - visible: 0 
// color: 7 - fill: 1 - name: _bNames - num: 126 - used: 0 - visible: 0 
// color: 7 - fill: 1 - name: _tValues - num: 127 - used: 0 - visible: 0 
// color: 7 - fill: 1 - name: _bValues - num: 128 - used: 0 - visible: 0 
// color: 7 - fill: 1 - name: Mask - num: 129 - used: 0 - visible: 0 
// color: 7 - fill: 1 - name: tAdjust - num: 131 - used: 0 - visible: 0 
// color: 7 - fill: 1 - name: bAdjust - num: 132 - used: 0 - visible: 0 
// color: 7 - fill: 1 - name: Drill_legend - num: 144 - used: 0 - visible: 0 
// color: 7 - fill: 1 - name: Notes - num: 150 - used: 0 - visible: 0 
// color: 7 - fill: 1 - name: HeatSink - num: 151 - used: 0 - visible: 0 
// color: 7 - fill: 1 - name: _bDocu - num: 152 - used: 0 - visible: 0 
// color: 7 - fill: 1 - name: FabDoc1 - num: 153 - used: 0 - visible: 0 
// color: 7 - fill: 1 - name: FabDoc2 - num: 154 - used: 0 - visible: 0 
// color: 7 - fill: 1 - name: FabDoc3 - num: 155 - used: 0 - visible: 0 
// color: 7 - fill: 1 - name: Contour - num: 199 - used: 0 - visible: 0 
// color: 1 - fill: 10 - name: 200bmp - num: 200 - used: 0 - visible: 0 
// color: 2 - fill: 10 - name: 201bmp - num: 201 - used: 0 - visible: 0 
// color: 3 - fill: 10 - name: 202bmp - num: 202 - used: 0 - visible: 0 
// color: 4 - fill: 10 - name: 203bmp - num: 203 - used: 0 - visible: 0 
// color: 5 - fill: 10 - name: 204bmp - num: 204 - used: 0 - visible: 0 
// color: 6 - fill: 10 - name: 205bmp - num: 205 - used: 0 - visible: 0 
// color: 7 - fill: 10 - name: 206bmp - num: 206 - used: 0 - visible: 0 
// color: 8 - fill: 10 - name: 207bmp - num: 207 - used: 0 - visible: 0 
// color: 9 - fill: 10 - name: 208bmp - num: 208 - used: 0 - visible: 0 
// color: 7 - fill: 1 - name: 209bmp - num: 209 - used: 0 - visible: 0 
// color: 7 - fill: 1 - name: 210bmp - num: 210 - used: 0 - visible: 0 
// color: 7 - fill: 1 - name: 211bmp - num: 211 - used: 0 - visible: 0 
// color: 7 - fill: 1 - name: 212bmp - num: 212 - used: 0 - visible: 0 
// color: 7 - fill: 1 - name: 213bmp - num: 213 - used: 0 - visible: 0 
// color: 7 - fill: 1 - name: 214bmp - num: 214 - used: 0 - visible: 0 
// color: 7 - fill: 1 - name: 215bmp - num: 215 - used: 0 - visible: 0 
// color: 7 - fill: 1 - name: 216bmp - num: 216 - used: 0 - visible: 0 
// color: 18 - fill: 1 - name: 217bmp - num: 217 - used: 0 - visible: 0 
// color: 19 - fill: 1 - name: 218bmp - num: 218 - used: 0 - visible: 0 
// color: 20 - fill: 1 - name: 219bmp - num: 219 - used: 0 - visible: 0 
// color: 21 - fill: 1 - name: 220bmp - num: 220 - used: 0 - visible: 0 
// color: 22 - fill: 1 - name: 221bmp - num: 221 - used: 0 - visible: 0 
// color: 23 - fill: 1 - name: 222bmp - num: 222 - used: 0 - visible: 0 
// color: 24 - fill: 1 - name: 223bmp - num: 223 - used: 0 - visible: 0 
// color: 25 - fill: 1 - name: 224bmp - num: 224 - used: 0 - visible: 0 
// color: 7 - fill: 1 - name: 225bmp - num: 225 - used: 0 - visible: 0 
// color: 7 - fill: 1 - name: 226bmp - num: 226 - used: 0 - visible: 0 
// color: 11 - fill: 1 - name: 227bmp - num: 227 - used: 0 - visible: 0 
// color: 10 - fill: 1 - name: 228bmp - num: 228 - used: 0 - visible: 0 
// color: 14 - fill: 1 - name: 229bmp - num: 229 - used: 0 - visible: 0 
// color: 12 - fill: 1 - name: 230bmp - num: 230 - used: 0 - visible: 0 
// color: 9 - fill: 1 - name: 231bmp - num: 231 - used: 0 - visible: 0 
// color: 7 - fill: 1 - name: Eagle3D_PG2 - num: 232 - used: 0 - visible: 0 
// color: 7 - fill: 1 - name: Eagle3D_PG3 - num: 233 - used: 0 - visible: 0 
// color: 7 - fill: 1 - name: Housing - num: 248 - used: 0 - visible: 0 
// color: 7 - fill: 1 - name: Edge - num: 249 - used: 0 - visible: 0 
// color: 3 - fill: 1 - name: Descript - num: 250 - used: 0 - visible: 0 
// color: 12 - fill: 11 - name: SMDround - num: 251 - used: 0 - visible: 0 
// color: 7 - fill: 1 - name: cooling - num: 254 - used: 0 - visible: 0 
// color: 7 - fill: 1 - name: routoute - num: 255 - used: 0 - visible: 0 
// ///////------------------------------------------------------------///////////

exit (cmd);
